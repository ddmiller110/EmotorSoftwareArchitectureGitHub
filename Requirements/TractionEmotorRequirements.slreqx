# TractionEmotorRequirements

## FunctionalRequirements (Functional)
The software shall achieve the following four pillars of top-level functional requirements for a traction e-motor application.
1. Torque Control & Accuracy
Description: The software shall implement Field Oriented Control (FOC) to provide independent control of flux and torque.
2. Operating Mode Management
The application shall manage transitions between defined operational states: INIT, STANDBY, READY_TO_DRIVE, DISCHARGE, and FAULT.
3. Flux Weakening & High-Speed Operation
Description: The software shall implement an Automatic Flux Weakening algorithm to extend the motor's operating range beyond the base speed.
4. System Observability & Protection
Description: The software shall implement a Thermal Power Derating function.

### Req3.1: SMDC function (Functional)
The System Mode Determination Component (SMDC) shall determine and output the overall system state. Additionally, the SMDC shall determine and output the following control signals:
- Inverter operational state
- Resolver reset request
- Bus voltage discharge command
- Rationale: To ensure consistent and centralized management of system-level operational modes and safety-critical control signals.
- Keywords: SMDC

### Req3.2: TDLC function (Functional)
The Torque Derating and Limiting Component (TDLC) shall:
- Calculate minimum and maximum torque constraints based on instantaneous DC bus voltage, motor speed, and derated maximum motor current.
- Limit the commanded torque to remain within the calculated torque constraints.
- Report the minimum and maximum available torque as well as the maximum allowable motor current.
- Rationale: To ensure torque commands respect physical and safety limits imposed by varying operating conditions and derating factors.
- Keywords: TDLC

### Req3.3: STMC function (Functional)
The Speed/Torque Mode Component (STMC) shall:
- Determine and set the operating mode of the traction e-motor to one of the following:
1. Speed control mode
2. Torque control mode
3. DC bus voltage control mode
- Limit the rate of change of the torque command to prevent excessive torque ramping.
- Rationale: To ensure correct mode selection for motor operation and to protect the system by controlling torque ramp rates.
- Keywords: STMC

### Req3.4: CRFC function (Functional)
The Currents Regulation and Feedback Component (CRFC) shall:
- Convert measured three-phase currents into d-axis and q-axis currents (Id and Iq) using Clarke and Park transforms.
- Calculate the PI controller gains (Kp and Ki​).
- Implement a PI controller with anti-windup to compute feedback voltage components that minimize current errors.
- Combine the feedback voltage components with feedforward voltage components to generate the desired d-axis and q-axis voltage commands (Ud and Uq​).
- Limit the Ud​ and Uq commands within the over-modulation range to prevent modulation saturation.
- Calculate and output the squared modulation index for use by other control functions.
- Rationale: To regulate motor currents accurately and ensure control signals remain within physical limits, enhancing system stability and performance.

### Req3.5: DQRC function (Functional)
DQRC: DQ Reference Current Calculation Component
The control algorithm shall compute DQ-axis reference currents such that the resulting steady-state motor torque output satisfies the following accuracy criteria throughout the specified drive cycle:
1. For commanded torque values greater than 100 Nm, the deviation between achieved and commanded torque shall not exceed ±3.5% of the commanded value.
2. For commanded torque values less than or equal to 100 Nm, the deviation between achieved and commanded torque shall not exceed ±4 Nm.
- Rationale: DQRC implements a collection of the following functions:
  - Generate the Id/Iq reference currents for the current controller to achieve required torque accuracy and maximum efficiency.
  - Calculate the feedforward commands of Vd/Vq and modulation index based on generated Id/Iq reference currents.
  - Calculate the instantaneous values of maximum torque limits for motoring and generating.
  - Calculate the power factor angle based on generated Id/Iq reference currents.

#### Req3.5.1: Stator Resistance Rs Calculation (Functional)
The control software shall use the stator resistance Rs​, calculated as a function of winding temperature, in the flux calculation to ensure accurate flux estimation.
The relationship between Rs​ and winding temperature shall conform to the equation specified below.
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Rs is the stator resistance to be calculated [ohm]
Rbase is the base stator resistance at room temperature[ohm]
T is the temperature of the stator winding [°C ]
α is the temperature coefficient [1/°C]
Tbase is the room temperature [°C ]
- Rationale: To improve flux estimation accuracy by accounting for temperature-dependent variations in stator resistance.

#### Req3.5.2: Maximum Flux Limit Calculation (Functional)
The control software shall calculate the maximum allowable flux linkage for the e-motor at any given operating point using the equation specified below:
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T – Torque Command
Rs - Stator Resistance
p - Number of Polepairs
ωe - Electric Frequency
VS - Modulation voltage calculated by Vdc and Maximum Modulation Index
- Rationale: To ensure safe and optimal motor operation within electrical and thermal limits.

#### Req3.5.3: Optimal Flux Calculation (Functional)
The control software shall determine the optimal flux linkage as a function of operating speed and torque demand as follows:
- When operating below base speed, the optimal flux linkage shall correspond to the flux level along the Maximum Torque per Ampere (MTPA) trajectory for the given torque command.
- When operating above base speed, the optimal flux linkage shall be set to the maximum allowable flux linkage.
This requirement fulfills Part I and Part IV of Requirement 1.5.4.
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- Rationale: To ensure optimal motor performance and efficiency across varying operating conditions.

#### Req3.5.4: Flux Weakening Control (Functional)
The Flux Weakening Control shall determine current and voltage control references in flux weakening region.
- In the constant torque region, the control software shall select the D-axis and Q-axis currents (Ids, Iqs​) to achieve Maximum Torque per Ampere (MTPA).
- In the flux weakening region, the commanded torque (Te_ref​) shall be limited to the maximum achievable torque (Te_max​) as defined by the Maximum Torque per Volt (MTPV) constraint.
Refer to the controller architecture diagram below for implementation details.
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The 2D calibration tables referenced in Part II shall be generated and calibrated using the Model-Based Calibration Toolbox.
Reference[1]: Bon Ho Bae, Patel N., Schulz, S., Seung Ki Sul , “New Field Weakening Technique for High Saliency Interior Permanent Magnet Motor” 38th IAS Annual Meeting. Conference Record of the Industry Applications Conference, Vol. 2, pp.898 905, 2003.
- Rationale: To maximize torque efficiency in the constant torque region and ensure torque commands remain within electrical constraints during flux weakening.

##### Req3.5.4.1: Id/Iq Current Reference LuT (Functional)
These two lookup tables are calibrated by Model-Based Calibration Toolbox

#### Req3.5.5: Feedforward Voltages Calculation (Functional)
The control software shall compute the steady-state stator voltages for the d- and q-axis using the sum of the voltage drop across the stator resistance and the product of flux linkage and electrical speed (in rad/s), as defined by the equations below.
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To achieve cross-decoupling of the d- and q-axis current controllers and to enhance dynamic performance and control stability, the system shall implement feedforward voltage control.
This feedforward control shall compensate for both the I×R (current × resistance) term and the Ψ×We​ (flux × electrical speed) term.
- Rationale: To reduce axis coupling effects and improve system response and robustness during dynamic operation.

#### Req3.5.6: Torque Limit Calculation (Functional)
The control software shall calculate the instantaneous torque limit as the minimum of the MTPA torque limit and the MTPV torque limit.
- The MTPA torque limit shall be determined from a calibrated 1D lookup table with Is_achieved​ as the input.
- The MTPV torque limit shall be determined from a 1D lookup table using the maximum allowed flux (flux_max​) as input.
- The value of flux_max shall be calculated as a function of instantaneous DC bus voltage, motor electrical speed, and Is_achieved​, as defined in the equation below.
- Only motoring mode shall be supported in this implementation.
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- Rationale: To ensure torque commands remain within safe and physically achievable limits under varying operating conditions.

### Req3.6: PSCC function (Functional)
The Position and Speed Calculation Component (PSCC) shall:
- Receive signals from the resolver and calculate the motor’s electrical position and speed.
- Utilize a redundant Phase-Locked Loop (PLL) to calculate motor position in the event of resolver failure.
- During Open Circuit (OC) testing, provide the position output as a command input to the motor controller.
- Rationale: To ensure accurate and reliable motor position and speed estimation under normal operation and fault conditions, and to support OC testing procedures.

### Req3.7: SFCC function (Functional)
The Switching Frequency Control Component (SFCC) shall:
- Calculate the PWM switching frequency for the current control loop based on control parameters.
- Determine the appropriate switching frequency during resolver calibration.
- Support manual override of the fast task switching frequency as required.
- Rationale: To optimize PWM switching frequency for control performance and accommodate special operating modes and manual adjustments.

### Req3.8: TAEC function (Functional)
The Torque Achieved Estimation Component (TAEC) shall:
- Estimate the achieved motor torque based on flux linkage and motor current measurements(primary layer).
- Compute power-based torque as an additional estimation method(independent monitoring layer).
- Monitor and verify the sign of the d-axis current (Id​) to support torque estimation validation.
- Rationale: To provide accurate and reliable estimation of motor torque for control and monitoring purposes.

#### Req3.8.1: FluxBasedTorque (Functional)
The FluxBasedTorque component shall calculate torque based on calculated e-motor flux linkages and e-motor currents.

#### Req3.8.2: DCPowerBasedTorque (Functional)
The DCPowerBasedTorque component shall calculate torque based on e-motor DC link power and e-motor's mechnical speed.

### Req3.9: PWMC function (Functional)
The PWM Generation Component (PWMC) shall:
- Determine the appropriate PWM mode based on control inputs and system state.
- Calculate duty cycles required for Space Vector PWM (SVPWM) operation.
- Estimate the instantaneous DC bus current.
- Determine and output the inverter state command and status signals.
- Rationale: To generate accurate PWM signals for inverter control while monitoring key electrical parameters and inverter status.

### Req3.10: ROCC function (Functional)
The Resolver Offset Calibration Component (ROCC) shall:
- Calibrate the resolver offset to correct measurement errors.
- Generate and output a resolver status signal indicating calibration and operational status.
- Rationale: To ensure accurate resolver position measurements and provide system status feedback.

### Req3.11: CSOC function (Functional)
The Current Sensor Offset Calibration Component (CSOC) shall perform calibration of the three-phase current sensors during system startup to correct offset errors.
- Rationale: To ensure accurate current measurements by compensating for sensor offsets prior to normal operation.

### Req3.12: VSOC function (Functional)
The Voltage Sensor Offset Calibration Component (VSOC) shall perform calibration of the high-voltage DC bus voltage sensors during system startup to correct offset errors.
- Rationale: To ensure accurate voltage measurements by compensating for sensor offsets prior to normal operation.

## PerformanceRequirements (Functional)

### Req6.1: Torque Transient Response (Functional)
The Currents Regulation and Feedback Component shall provide a torque transient response that meets the following performance criteria when subjected to a step change in the torque command:
1. The actual torque shall reach the new commanded torque value within 10 milliseconds.
2. The torque overshoot shall not exceed 5% of the commanded value.
- Rationale: Ensuring the torque controller provides fast and stable transient response to torque demand changes, supporting dynamic performance requirements.

### Req6.2: Torque Accuracy (Functional)
The DQRC control algorithm shall compute DQ-axis reference currents such that the resulting steady-state motor torque output satisfies the following accuracy criteria throughout the specified drive cycle:
1. For commanded torque values greater than 100 Nm, the deviation between achieved and commanded torque shall not exceed ±3% of the commanded value.
2. For commanded torque values less than or equal to 100 Nm, the deviation between achieved and commanded torque shall not exceed ±4 Nm.
- Rationale: Ensuring accurate steady-state torque control across the drive cycle is critical to meet system-level performance, drivability, and energy efficiency requirements.

## Safety Goal (Container)

### SafetyGoal_01: Prevent Unintended Lead Torque (Functional)
The vehicle shall not accelerate autonomously without a valid driver command.
- Rationale: The customer expects that if they aren't touching the pedal, the car stays still. If the motor suddenly produces 200Nm of torque while at a stoplight, that is a catastrophic failure.

## FunctionalSafetyRequirements (Container)

### FuSa_Req_01: Transition to a Safe State (Functional)
The Motor Control Unit (MCU) shall transition to a safe state (Torque_Off) if the actual torque exceeds the requested torque by >50 Nm for more than 150 ms.
- Rationale: The Motor Control Unit (MCU) shall transition to a Safe State (Safe Torque Off) if the Actual Torque exceeds the Requested Torque by 50 Nm for more than 200 ms.

## SoftwareSafetyRequirements (Functional)

### SoftwareSafetyReq_01: Monitor Torque (Functional)
The software shall implement a 3-layer Monitoring architecture.
Layer 2 (level 2) shall independently estimate motor torque using measured phase currents (i_a, i_b, i_c), DC link voltage, DC link current, and calculated flux linkages.
- Rationale: We can't trust the main control loop to grade its own homework. We need a "Shadow Algorithm" that calculates torque differently than the main FOC loop.

## StakeholderRequirements (Informational)
1. Driveability & Performance
These requirements define the "feel" of the car.
- Linear Torque Delivery: The motor control software shall provide a linear relationship between the accelerator pedal position and the motor torque output to ensure predictable acceleration.
- NVH (Noise, Vibration, Harshness): The inverter switching strategy shall minimize acoustic noise and torque ripple to prevent cabin resonances at speeds between 0 and 16,000 rpm.
- Regenerative Braking Feel: The system shall blend regenerative braking with friction braking seamlessly, ensuring no "torque surge" when the driver releases the accelerator.
2. Efficiency & Range
- Drive Cycle Efficiency: The software shall optimize the d/q current trajectories to achieve a minimum of 96% inverter efficiency over the WLTP (Worldwide Harmonized Light Vehicles Test Procedure) cycle.
- Low-Power State (Sleep): The motor controller software shall enter a "Deep Sleep" state within 30 seconds of vehicle ignition-off, consuming less than 2mA of current.
3. Functional Safety
These are the ASIL D modules.
- Unintended Torque Mitigation: The system shall prevent unintended positive or negative torque that exceeds the driver’s intent by more than 50Nm or 10% of peak torque.
- High Voltage (HV) Interlock: The software shall monitor the High Voltage Interlock Loop (HVIL) and immediately disable the inverter PWM if a hardware breach or disconnect is detected.
- Cybersecurity: The motor control application shall only accept torque commands from authenticated and integrity-checked messages on the vehicle CAN/Ethernet bus.
4. Vehicle Integration & Service
- Over-the-Air (OTA) Updates: The software architecture shall support secure A/B memory swapping to allow for firmware updates without vehicle downtime.
- Unified Diagnostic Services (UDS): The software shall support ISO 14229 (UDS) for reading fault codes (DTCs), snapshots of motor data at the time of a fault, and software versioning.
- Thermal Self-Protection: The software shall implement a derating strategy to protect the motor and inverter from permanent damage if temperatures exceed 150 celcius (motor) or 125 celcius(IGBT/SiC).
